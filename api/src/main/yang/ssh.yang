module ssh {
    yang-version 1;
    namespace "urn:opendaylight:params:xml:ns:yang:ssh";
    prefix "ssh";

    revision "2015-01-05" {
        description "Initial revision of ssh model";
    }

    rpc connect{
     input{
         leaf ip {
             type string;
         }
         leaf port{
           type int32;
           default 22;
         }
         leaf user{
           type string;
         }
         leaf password{
           type string;
         }
     }
     output{
          leaf status{
              type string;
          }
          leaf sessionID{
              type string;
          }
     }
    }

    rpc command {
    input {
        leaf sessionID {
            type string;
        }
        leaf command{
          type string;
        }
        leaf timeout{
        	type int64;
        	default 30000;
        	description "This api terminates the connection if a timeout occurs while reading from server.
        		You can set the timeout in miliseconds, or you can ommit this value which then will be defaulted to 30 seconds";
        }
    }
    output {
        leaf response {
            type string;
        }
    }
}

rpc terminateConnection{
  input{
    leaf sessionID{
          type string;
        }

  }
  output{
    leaf response{
      type string;
    }
  }
}

}
